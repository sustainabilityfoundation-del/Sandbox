# Pump specification
Fixture covering datatypes, enumerations, XHTML, hierarchy, relations and groups

# Specification: Pump specification

## so-h1: Hydraulics

### so-1: Flow rate
The pump shall deliver at least 40 l/min at 2 bar.
See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.
Unsafe link
- Rationale: Process demand
- Priority: High
- Cycles: 100000
- Mass budget: 12.5
- Safety relevant: true
- Due: 2027-03-31T00:00:00.000Z
- Satisfied by test -> so-2

### so-2: Inlet pressure
The inlet shall tolerate 0.5 bar to 3 bar.
- Priority: Low
- Derived from -> so-1
